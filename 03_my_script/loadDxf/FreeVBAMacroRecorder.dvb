Attribute VB_Name = "NewMacros"
Option Explicit
 
Public Sub AddLine()
Dim oAcadLine As AcadLine
Dim StartPoint(0 To 2) As Double
Dim EndPoint(0 To 2) As Double
 
  StartPoint(0) = 0
  StartPoint(1) = 0
  StartPoint(2) = 0
  EndPoint(0) = 4
  EndPoint(1) = 4
  EndPoint(2) = 0
 
  Set oAcadLine = ThisDrawing.ModelSpace.AddLine(StartPoint, EndPoint)
 
  With oAcadLine
    .Color = acByLayer
    .Layer = "0"
    .Linetype = "ByLayer"
    .LinetypeScale = 1
    .Lineweight = -1
    .Thickness = 0
  End With
End Sub

Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
Option Explicit
'*** Copyright 2001 - Joe Sutphin - All Rights Reserved ***'
'
' You are hereby granted the right to use this code
' however you see fit. By accepting this source code you
' agree that you will not re-post or re-distribute this
' work as your own work even if you have modified it. If
' you should want to re-post or re-distribute this code
' and any modifications to it, you must continue to give
' full credit to me as the original author
'
'*** Copyright 2001 - Joe Sutphin - All Rights Reserved ***'

Private bRecorderStarted As Boolean

Private objVBE As Object
Private objVBComponent As Object

Const QUOTE = """"

Public Sub Record()
  InitVBE
  NewModule
  bRecorderStarted = True
End Sub

Private Sub InitVBE()
  Set objVBE = Application.VBE
End Sub

Private Sub NewModule()
  If Not CheckForModule Then
    'module does not exist, so let's create it
    With objVBE.ActiveVBProject
      With .VBComponents.Add(vbext_ct_StdModule)
        .Name = "NewMacros"
      End With
    End With
  End If
End Sub

Private Function CheckForModule() As Boolean
Dim objVBComponent As VBIDE.VBComponent

'assume failure
CheckForModule = False

  'check for NewMacros module
  For Each objVBComponent In objVBE.ActiveVBProject.VBComponents
    If objVBComponent.Name = "NewMacros" Then
      CheckForModule = True
      Exit Function
    End If
  Next objVBComponent
End Function

Private Sub AddMacro_Arc(Object As AcadObject)
Dim oArc As AcadArc
Dim strAnswer As String
Dim strSpace As String

  strAnswer = InputBox("Enter macro name", "Macro Name Entry")
  
  If strAnswer = "" Then
    'user cancelled, turn off recording
    bRecorderStarted = False
    Exit Sub
  End If
  
  'cast object to proper data type
  Set oArc = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadArc As AcadArc"
    .InsertLines (.CountOfLines + 1), "Dim Center(0 to 2) As Double"
    .InsertLines (.CountOfLines + 1), "Dim Radius As Double"
    .InsertLines (.CountOfLines + 1), "Dim StartAngle As Double"
    .InsertLines (.CountOfLines + 1), "Dim EndAngle As Double"
    .InsertLines (.CountOfLines + 1), " "
    .InsertLines (.CountOfLines + 1), "  Center(0) = " & oArc.center(0)
    .InsertLines (.CountOfLines + 1), "  Center(1) = " & oArc.center(1)
    .InsertLines (.CountOfLines + 1), "  Center(2) = " & oArc.center(2)
    .InsertLines (.CountOfLines + 1), "  Radius = " & oArc.radius
    .InsertLines (.CountOfLines + 1), "  StartAngle = " & oArc.StartAngle
    .InsertLines (.CountOfLines + 1), "  EndAngle = " & oArc.EndAngle
    .InsertLines (.CountOfLines + 1), " "
    .InsertLines (.CountOfLines + 1), "  Set oAcadArc = ThisDrawing." & strSpace & ".AddArc(Center, Radius, StartAngle, EndAngle)"
    .InsertLines (.CountOfLines + 1), " "
    .InsertLines (.CountOfLines + 1), "  With oAcadArc"
    .InsertLines (.CountOfLines + 1), "    .Color = " & oArc.Color
    .InsertLines (.CountOfLines + 1), "    .Layer = " & QUOTE & oArc.Layer & QUOTE
    .InsertLines (.CountOfLines + 1), "    .Linetype = " & QUOTE & oArc.Linetype & QUOTE
    .InsertLines (.CountOfLines + 1), "    .LinetypeScale = " & oArc.LinetypeScale
    .InsertLines (.CountOfLines + 1), "    .Lineweight = " & oArc.Lineweight
    .InsertLines (.CountOfLines + 1), "    .Thickness = " & oArc.Thickness
    .InsertLines (.CountOfLines + 1), "  End With"
    .InsertLines (.CountOfLines + 1), "End Sub"
    .InsertLines (.CountOfLines + 1), " "
  End With
  
  'turn off recorder
  bRecorderStarted = False
End Sub

Private Sub AddMacro_Circle(Object As AcadObject)
Dim oCircle As AcadCircle
Dim strAnswer As String
Dim strSpace As String

  strAnswer = InputBox("Enter macro name", "Macro Name Entry")
  
  If strAnswer = "" Then
    'user cancelled, turn off recording
    bRecorderStarted = False
    Exit Sub
  End If
  
  'cast object to proper data type
  Set oCircle = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadCircle As AcadCircle"
    .InsertLines (.CountOfLines + 1), "Dim Center(0 to 2) As Double"
    .InsertLines (.CountOfLines + 1), "Dim Radius As Double"
    .InsertLines (.CountOfLines + 1), " "
    .InsertLines (.CountOfLines + 1), "  Center(0) = " & oCircle.center(0)
    .InsertLines (.CountOfLines + 1), "  Center(1) = " & oCircle.center(1)
    .InsertLines (.CountOfLines + 1), "  Center(2) = " & oCircle.center(2)
    .InsertLines (.CountOfLines + 1), "  Radius = " & oCircle.radius
    .InsertLines (.CountOfLines + 1), " "
    .InsertLines (.CountOfLines + 1), "  Set oAcadCircle = ThisDrawing." & strSpace & ".AddCircle(Center, Radius)"
    .InsertLines (.CountOfLines + 1), " "
    .InsertLines (.CountOfLines + 1), "  With oAcadCircle"
    .InsertLines (.CountOfLines + 1), "    .Color = " & oCircle.Color
    .InsertLines (.CountOfLines + 1), "    .Layer = " & QUOTE & oCircle.Layer & QUOTE
    .InsertLines (.CountOfLines + 1), "    .Linetype = " & QUOTE & oCircle.Linetype & QUOTE
    .InsertLines (.CountOfLines + 1), "    .LinetypeScale = " & oCircle.LinetypeScale
    .InsertLines (.CountOfLines + 1), "    .Lineweight = " & oCircle.Lineweight
    .InsertLines (.CountOfLines + 1), "    .Thickness = " & oCircle.Thickness
    .InsertLines (.CountOfLines + 1), "  End With"
    .InsertLines (.CountOfLines + 1), "End Sub"
    .InsertLines (.CountOfLines + 1), " "
  End With
  
  'turn off recorder
  bRecorderStarted = False
End Sub

Private Sub AddMacro_Ellipse(Object As AcadObject)
Dim oEllipse As AcadEllipse
Dim strAnswer As String
Dim strSpace As String

  strAnswer = InputBox("Enter macro name", "Macro Name Entry")
  
  If strAnswer = "" Then
    'user cancelled, turn off recording
    bRecorderStarted = False
    Exit Sub
  End If
  
  'cast object to proper data type
  Set oEllipse = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadEllipse As AcadEllipse"
    .InsertLines (.CountOfLines + 1), "Dim Center(0 to 2) As Double"
    .InsertLines (.CountOfLines + 1), "Dim MajorAxis(0 to 2) As Double"
    .InsertLines (.CountOfLines + 1), "Dim RadiusRatio As Double"
    .InsertLines (.CountOfLines + 1), " "
    .InsertLines (.CountOfLines + 1), "  Center(0) = " & oEllipse.center(0)
    .InsertLines (.CountOfLines + 1), "  Center(1) = " & oEllipse.center(1)
    .InsertLines (.CountOfLines + 1), "  Center(2) = " & oEllipse.center(2)
    .InsertLines (.CountOfLines + 1), "  MajorAxis(0) = " & oEllipse.MajorAxis(0)
    .InsertLines (.CountOfLines + 1), "  MajorAxis(1) = " & oEllipse.MajorAxis(1)
    .InsertLines (.CountOfLines + 1), "  MajorAxis(2) = " & oEllipse.MajorAxis(2)
    .InsertLines (.CountOfLines + 1), "  RadiusRatio = " & oEllipse.RadiusRatio
    .InsertLines (.CountOfLines + 1), " "
    .InsertLines (.CountOfLines + 1), "  Set oAcadEllipse = ThisDrawing." & strSpace & ".AddEllipse(Center, MajorAxis, RadiusRatio)"
    .InsertLines (.CountOfLines + 1), " "
    .InsertLines (.CountOfLines + 1), "  With oAcadEllipse"
    .InsertLines (.CountOfLines + 1), "    .Color = " & oEllipse.Color
    .InsertLines (.CountOfLines + 1), "    .Layer = " & QUOTE & oEllipse.Layer & QUOTE
    .InsertLines (.CountOfLines + 1), "    .Linetype = " & QUOTE & oEllipse.Linetype & QUOTE
    .InsertLines (.CountOfLines + 1), "    .LinetypeScale = " & oEllipse.LinetypeScale
    .InsertLines (.CountOfLines + 1), "    .Lineweight = " & oEllipse.Lineweight
    .InsertLines (.CountOfLines + 1), "  End With"
    .InsertLines (.CountOfLines + 1), "End Sub"
    .InsertLines (.CountOfLines + 1), " "
  End With
  
  'turn off recorder
  bRecorderStarted = False
End Sub

Private Sub AddMacro_Line(Object As AcadObject)
Dim oLine As AcadLine
Dim strAnswer As String
Dim strSpace As String

  strAnswer = InputBox("Enter macro name", "Macro Name Entry")
  
  If strAnswer = "" Then
    'user cancelled, turn off recording
    bRecorderStarted = False
    Exit Sub
  End If
  
  'cast object to proper data type
  Set oLine = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadLine As AcadLine"
    .InsertLines (.CountOfLines + 1), "Dim StartPoint(0 to 2) As Double"
    .InsertLines (.CountOfLines + 1), "Dim EndPoint(0 to 2) As Double"
    .InsertLines (.CountOfLines + 1), " "
    .InsertLines (.CountOfLines + 1), "  StartPoint(0) = " & oLine.StartPoint(0)
    .InsertLines (.CountOfLines + 1), "  StartPoint(1) = " & oLine.StartPoint(1)
    .InsertLines (.CountOfLines + 1), "  StartPoint(2) = " & oLine.StartPoint(2)
    .InsertLines (.CountOfLines + 1), "  EndPoint(0) = " & oLine.EndPoint(0)
    .InsertLines (.CountOfLines + 1), "  EndPoint(1) = " & oLine.EndPoint(1)
    .InsertLines (.CountOfLines + 1), "  EndPoint(2) = " & oLine.EndPoint(2)
    .InsertLines (.CountOfLines + 1), " "
    .InsertLines (.CountOfLines + 1), "  Set oAcadLine = ThisDrawing." & strSpace & ".AddLine(StartPoint, EndPoint)"
    .InsertLines (.CountOfLines + 1), " "
    .InsertLines (.CountOfLines + 1), "  With oAcadLine"
    .InsertLines (.CountOfLines + 1), "    .Color = " & oLine.Color
    .InsertLines (.CountOfLines + 1), "    .Layer = " & QUOTE & oLine.Layer & QUOTE
    .InsertLines (.CountOfLines + 1), "    .Linetype = " & QUOTE & oLine.Linetype & QUOTE
    .InsertLines (.CountOfLines + 1), "    .LinetypeScale = " & oLine.LinetypeScale
    .InsertLines (.CountOfLines + 1), "    .Lineweight = " & oLine.Lineweight
    .InsertLines (.CountOfLines + 1), "    .Thickness = " & oLine.Thickness
    .InsertLines (.CountOfLines + 1), "  End With"
    .InsertLines (.CountOfLines + 1), "End Sub"
    .InsertLines (.CountOfLines + 1), " "
  End With
  
  'turn off recorder
  bRecorderStarted = False
End Sub

Private Sub AddMacro_Point(Object As AcadObject)
Dim oPoint As AcadPoint
Dim strAnswer As String
Dim strSpace As String

  strAnswer = InputBox("Enter macro name", "Macro Name Entry")
  
  If strAnswer = "" Then
    'user cancelled, turn off recording
    bRecorderStarted = False
    Exit Sub
  End If
  
  'cast object to proper data type
  Set oPoint = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadPoint As AcadPoint"
    .InsertLines (.CountOfLines + 1), "Dim Point(0 to 2) As Double"
    .InsertLines (.CountOfLines + 1), " "
    .InsertLines (.CountOfLines + 1), "  Point(0) = " & oPoint.Coordinates(0)
    .InsertLines (.CountOfLines + 1), "  Point(1) = " & oPoint.Coordinates(1)
    .InsertLines (.CountOfLines + 1), "  Point(2) = " & oPoint.Coordinates(2)
    .InsertLines (.CountOfLines + 1), " "
    .InsertLines (.CountOfLines + 1), "  Set oAcadPoint = ThisDrawing." & strSpace & ".AddPoint(Point)"
    .InsertLines (.CountOfLines + 1), " "
    .InsertLines (.CountOfLines + 1), "  With oAcadPoint"
    .InsertLines (.CountOfLines + 1), "    .Color = " & oPoint.Color
    .InsertLines (.CountOfLines + 1), "    .Layer = " & QUOTE & oPoint.Layer & QUOTE
    .InsertLines (.CountOfLines + 1), "    .Linetype = " & QUOTE & oPoint.Linetype & QUOTE
    .InsertLines (.CountOfLines + 1), "    .LinetypeScale = " & oPoint.LinetypeScale
    .InsertLines (.CountOfLines + 1), "    .Lineweight = " & oPoint.Lineweight
    .InsertLines (.CountOfLines + 1), "    .Thickness = " & oPoint.Thickness
    .InsertLines (.CountOfLines + 1), "  End With"
    .InsertLines (.CountOfLines + 1), "End Sub"
    .InsertLines (.CountOfLines + 1), " "
  End With
  
  'turn off recorder
  bRecorderStarted = False
End Sub

Private Sub AddMacro_Polyline(Object As AcadObject)
Dim oLWPolyline As AcadLWPolyline
Dim strAnswer As String
Dim strSpace As String
Dim lngVertices As Long

  strAnswer = InputBox("Enter macro name", "Macro Name Entry")
  
  If strAnswer = "" Then
    'user cancelled, turn off recording
    bRecorderStarted = False
    Exit Sub
  End If
  
  'cast object to proper data type
  Set oLWPolyline = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadLWPolyline As AcadLWPolyline"
    .InsertLines (.CountOfLines + 1), "Dim VerticesList(" & UBound(oLWPolyline.Coordinates) & ")" & " As Double"
    .InsertLines (.CountOfLines + 1), " "
    
    For lngVertices = 0 To UBound(oLWPolyline.Coordinates)
      .InsertLines (.CountOfLines + 1), "  VerticesList(" & lngVertices & ") = " & oLWPolyline.Coordinates(lngVertices)
    Next lngVertices
    
    .InsertLines (.CountOfLines + 1), " "
    .InsertLines (.CountOfLines + 1), "  Set oAcadLWPolyline = ThisDrawing." & strSpace & ".AddLightweightPolyline(VerticesList)"
    .InsertLines (.CountOfLines + 1), " "
    .InsertLines (.CountOfLines + 1), "  With oAcadLWPolyline"
    .InsertLines (.CountOfLines + 1), "    .Closed = " & oLWPolyline.Closed
    .InsertLines (.CountOfLines + 1), "    .Color = " & oLWPolyline.Color
    .InsertLines (.CountOfLines + 1), "    .Layer = " & QUOTE & oLWPolyline.Layer & QUOTE
    .InsertLines (.CountOfLines + 1), "    .Linetype = " & QUOTE & oLWPolyline.Linetype & QUOTE
    .InsertLines (.CountOfLines + 1), "    .LinetypeScale = " & oLWPolyline.LinetypeScale
    .InsertLines (.CountOfLines + 1), "    .Lineweight = " & oLWPolyline.Lineweight
    .InsertLines (.CountOfLines + 1), "    .Thickness = " & oLWPolyline.Thickness
    .InsertLines (.CountOfLines + 1), "  End With"
    .InsertLines (.CountOfLines + 1), "End Sub"
    .InsertLines (.CountOfLines + 1), " "
  End With
  
  'turn off recorder
  bRecorderStarted = False
End Sub

Private Sub AddMacro_Ray(Object As AcadObject)
Dim oRay As AcadRay
Dim strAnswer As String
Dim strSpace As String

  strAnswer = InputBox("Enter macro name", "Macro Name Entry")
  
  If strAnswer = "" Then
    'user cancelled, turn off recording
    bRecorderStarted = False
    Exit Sub
  End If
  
  'cast object to proper data type
  Set oRay = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadRay As AcadRay"
    .InsertLines (.CountOfLines + 1), "Dim Point1(0 to 2) As Double"
    .InsertLines (.CountOfLines + 1), "Dim Point2(0 to 2) As Double"
    .InsertLines (.CountOfLines + 1), "Dim DirectionVector(0 to 2) As Double"
    .InsertLines (.CountOfLines + 1), " "
    .InsertLines (.CountOfLines + 1), "  Point1(0) = " & oRay.BasePoint(0)
    .InsertLines (.CountOfLines + 1), "  Point1(1) = " & oRay.BasePoint(1)
    .InsertLines (.CountOfLines + 1), "  Point1(2) = " & oRay.BasePoint(2)
    .InsertLines (.CountOfLines + 1), "  Point2(0) = " & oRay.SecondPoint(0)
    .InsertLines (.CountOfLines + 1), "  Point2(1) = " & oRay.SecondPoint(1)
    .InsertLines (.CountOfLines + 1), "  Point2(2) = " & oRay.SecondPoint(2)
    .InsertLines (.CountOfLines + 1), " "
    .InsertLines (.CountOfLines + 1), "  Set oAcadRay = ThisDrawing." & strSpace & ".AddRay(Point1, Point2)"
    .InsertLines (.CountOfLines + 1), " "
    .InsertLines (.CountOfLines + 1), "  With oAcadRay"
    .InsertLines (.CountOfLines + 1), "    .Color = " & oRay.Color
    .InsertLines (.CountOfLines + 1), "    .Layer = " & QUOTE & oRay.Layer & QUOTE
    .InsertLines (.CountOfLines + 1), "    .Linetype = " & QUOTE & oRay.Linetype & QUOTE
    .InsertLines (.CountOfLines + 1), "    .LinetypeScale = " & oRay.LinetypeScale
    .InsertLines (.CountOfLines + 1), "    .Lineweight = " & oRay.Lineweight
    .InsertLines (.CountOfLines + 1), "  End With"
    .InsertLines (.CountOfLines + 1), "End Sub"
    .InsertLines (.CountOfLines + 1), " "
  End With
  
  'turn off recorder
  bRecorderStarted = False
End Sub

Private Sub AddMacro_Spline(Object As AcadObject)
Dim oSpline As AcadSpline
Dim strAnswer As String
Dim strSpace As String
Dim lngFitPoints As Long

  strAnswer = InputBox("Enter macro name", "Macro Name Entry")
  
  If strAnswer = "" Then
    'user cancelled, turn off recording
    bRecorderStarted = False
    Exit Sub
  End If
  
  'cast object to proper data type
  Set oSpline = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadSpline As AcadSpline"
    .InsertLines (.CountOfLines + 1), "Dim StartTangent(0 to 2) As Double"
    .InsertLines (.CountOfLines + 1), "Dim EndTangent(0 to 2) As Double"
    .InsertLines (.CountOfLines + 1), "Dim FitPoints(" & UBound(oSpline.FitPoints) & ")" & " As Double"
    .InsertLines (.CountOfLines + 1), " "
    .InsertLines (.CountOfLines + 1), "  StartTangent(0) = " & oSpline.StartTangent(0)
    .InsertLines (.CountOfLines + 1), "  StartTangent(1) = " & oSpline.StartTangent(1)
    .InsertLines (.CountOfLines + 1), "  StartTangent(2) = " & oSpline.StartTangent(2)
    .InsertLines (.CountOfLines + 1), "  EndTangent(0) = " & oSpline.EndTangent(0)
    .InsertLines (.CountOfLines + 1), "  EndTangent(1) = " & oSpline.EndTangent(1)
    .InsertLines (.CountOfLines + 1), "  EndTangent(2) = " & oSpline.EndTangent(2)
    
    For lngFitPoints = 0 To UBound(oSpline.FitPoints)
      .InsertLines (.CountOfLines + 1), "  FitPoints(" & lngFitPoints & ") = " & oSpline.FitPoints(lngFitPoints)
    Next lngFitPoints
    
    .InsertLines (.CountOfLines + 1), " "
    .InsertLines (.CountOfLines + 1), "  Set oAcadSpline = ThisDrawing." & strSpace & ".AddSpline(FitPoints, StartTangent, EndTangent)"
    .InsertLines (.CountOfLines + 1), " "
    .InsertLines (.CountOfLines + 1), "  With oAcadSpline"
    .InsertLines (.CountOfLines + 1), "    .Color = " & oSpline.Color
    .InsertLines (.CountOfLines + 1), "    .Layer = " & QUOTE & oSpline.Layer & QUOTE
    .InsertLines (.CountOfLines + 1), "    .Linetype = " & QUOTE & oSpline.Linetype & QUOTE
    .InsertLines (.CountOfLines + 1), "    .LinetypeScale = " & oSpline.LinetypeScale
    .InsertLines (.CountOfLines + 1), "    .Lineweight = " & oSpline.Lineweight
    .InsertLines (.CountOfLines + 1), "  End With"
    .InsertLines (.CountOfLines + 1), "End Sub"
    .InsertLines (.CountOfLines + 1), " "
  End With
  
  'turn off recorder
  bRecorderStarted = False
End Sub

Private Sub AddMacro_MText(Object As AcadObject)
Dim oMText As AcadMText
Dim strAnswer As String
Dim strSpace As String

  strAnswer = InputBox("Enter macro name", "Macro Name Entry")
  
  If strAnswer = "" Then
    'user cancelled, turn off recording
    bRecorderStarted = False
    Exit Sub
  End If
  
  'cast object to proper data type
  Set oMText = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadMText As AcadMText"
    .InsertLines (.CountOfLines + 1), "Dim InsertionPoint(0 to 2) As Double"
    .InsertLines (.CountOfLines + 1), "Dim Width As Double"
    .InsertLines (.CountOfLines + 1), "Dim Text As String"
    .InsertLines (.CountOfLines + 1), " "
    .InsertLines (.CountOfLines + 1), "  InsertionPoint(0) = " & oMText.InsertionPoint(0)
    .InsertLines (.CountOfLines + 1), "  InsertionPoint(1) = " & oMText.InsertionPoint(1)
    .InsertLines (.CountOfLines + 1), "  InsertionPoint(2) = " & oMText.InsertionPoint(2)
    .InsertLines (.CountOfLines + 1), " "
    .InsertLines (.CountOfLines + 1), "  Width = " & oMText.Width
    .InsertLines (.CountOfLines + 1), "  Text = " & QUOTE & oMText.TextString & QUOTE
    .InsertLines (.CountOfLines + 1), " "
    .InsertLines (.CountOfLines + 1), "  Set oAcadMText = ThisDrawing." & strSpace & ".AddMText(InsertionPoint, Width, Text)"
    .InsertLines (.CountOfLines + 1), " "
    .InsertLines (.CountOfLines + 1), "  With oAcadMText"
    .InsertLines (.CountOfLines + 1), "    .Color = " & oMText.Color
    .InsertLines (.CountOfLines + 1), "    .Layer = " & QUOTE & oMText.Layer & QUOTE
    .InsertLines (.CountOfLines + 1), "    .Linetype = " & QUOTE & oMText.Linetype & QUOTE
    .InsertLines (.CountOfLines + 1), "    .LinetypeScale = " & oMText.LinetypeScale
    .InsertLines (.CountOfLines + 1), "    .Lineweight = " & oMText.Lineweight
    .InsertLines (.CountOfLines + 1), "  End With"
    .InsertLines (.CountOfLines + 1), "End Sub"
    .InsertLines (.CountOfLines + 1), " "
  End With
  
  'turn off recorder
  bRecorderStarted = False
End Sub

Private Sub AddMacro_Text(Object As AcadObject)
Dim oText As AcadText
Dim strAnswer As String
Dim strSpace As String

  strAnswer = InputBox("Enter macro name", "Macro Name Entry")
  
  If strAnswer = "" Then
    'user cancelled, turn off recording
    bRecorderStarted = False
    Exit Sub
  End If
  
  'cast object to proper data type
  Set oText = Object
  
  'figure out the proper space
  If ThisDrawing.ActiveSpace Then
    'model space is active
    strSpace = "ModelSpace"
    
    Else
      strSpace = "PaperSpace"
  End If

  With objVBE.ActiveVBProject.VBComponents("NewMacros").CodeModule
    .InsertLines (.CountOfLines + 1), "Public Sub " & strAnswer & "()"
    .InsertLines (.CountOfLines + 1), "Dim oAcadText As AcadText"
    .InsertLines (.CountOfLines + 1), "Dim InsertionPoint(0 to 2) As Double"
    .InsertLines (.CountOfLines + 1), "Dim Height As Double"
    .InsertLines (.CountOfLines + 1), "Dim TextString As String"
    .InsertLines (.CountOfLines + 1), " "
    .InsertLines (.CountOfLines + 1), "  InsertionPoint(0) = " & oText.InsertionPoint(0)
    .InsertLines (.CountOfLines + 1), "  InsertionPoint(1) = " & oText.InsertionPoint(1)
    .InsertLines (.CountOfLines + 1), "  InsertionPoint(2) = " & oText.InsertionPoint(2)
    .InsertLines (.CountOfLines + 1), " "
    .InsertLines (.CountOfLines + 1), "  Height = " & oText.Height
    .InsertLines (.CountOfLines + 1), "  TextString = " & QUOTE & oText.TextString & QUOTE
    .InsertLines (.CountOfLines + 1), " "
    .InsertLines (.CountOfLines + 1), "  Set oAcadText = ThisDrawing." & strSpace & ".AddText(TextString, InsertionPoint, Height)"
    .InsertLines (.CountOfLines + 1), " "
    .InsertLines (.CountOfLines + 1), "  With oAcadText"
    .InsertLines (.CountOfLines + 1), "    .Color = " & oText.Color
    .InsertLines (.CountOfLines + 1), "    .Layer = " & QUOTE & oText.Layer & QUOTE
    .InsertLines (.CountOfLines + 1), "    .Linetype = " & QUOTE & oText.Linetype & QUOTE
    .InsertLines (.CountOfLines + 1), "    .LinetypeScale = " & oText.LinetypeScale
    .InsertLines (.CountOfLines + 1), "    .Lineweight = " & oText.Lineweight
    .InsertLines (.CountOfLines + 1), "    .Thickness = " & oText.Thickness
    .InsertLines (.CountOfLines + 1), "  End With"
    .InsertLines (.CountOfLines + 1), "End Sub"
    .InsertLines (.CountOfLines + 1), " "
  End With
  
  'turn off recorder
  bRecorderStarted = False
End Sub

Private Sub AcadDocument_EndCommand(ByVal CommandName As String)
Dim oAcadObject As AcadObject

  If bRecorderStarted Then
    If CommandName = "PLINE" Then
      With ThisDrawing.ModelSpace
        Set oAcadObject = ThisDrawing.ObjectIdToObject(.Item(.Count - 1).ObjectID)
        AddMacro_Polyline oAcadObject
      End With
    End If
  End If
End Sub

Private Sub AcadDocument_ObjectAdded(ByVal Object As Object)
  'if Caption is "Stop" then we're in record mode
  If bRecorderStarted Then
    Select Case UCase(Object.ObjectName)
      'Arc object added
      Case "ACDBARC"
        AddMacro_Arc Object
        
      'Circle object added
      Case "ACDBCIRCLE"
        AddMacro_Circle Object
        
      'Ellipse object added
      Case "ACDBELLIPSE"
        AddMacro_Ellipse Object
     
      'Line object added
      Case "ACDBLINE"
        AddMacro_Line Object
      
      'Point object added
      Case "ACDBPOINT"
        AddMacro_Point Object
          
      'Ray object added
      Case "ACDBRAY"
        AddMacro_Ray Object
          
      'Spline object added
      Case "ACDBSPLINE"
        AddMacro_Spline Object
          
      'MText object added
      Case "ACDBMTEXT"
        AddMacro_MText Object
        
      'Text object added
      Case "ACDBTEXT"
        AddMacro_Text Object
    End Select
  End If

  'uncomment to determine exact object name used by AutoCAD
  'Debug.Print Object.ObjectName
End Sub
