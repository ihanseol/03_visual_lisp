Attribute VB_Name = "Module1"

Function GetFrenchDoors()
    Dim ssFrench As AcadSelectionSet
    Dim FilterType(0) As Integer
    Dim FilterData(0) As Variant
    
    FilterType(0) = 2
    FilterData(0) = "Door - French"
    
    Call ClerSelectionSet
    Set ssFrench = ThisDrawing.SelectionSets.Add("French")
    ssFrench.Select acSelectionSetAll, , , FilterType, FilterData
    
    GetFrenchDoors = ssFrench.Count
End Function
