; 여러 스냅을 같이 쓰시고자 할 땐 아래 스냅코드를 합산한 숫자를 기입하시면됩니다.
; (예 : 끝점, 중간점, 중심점 일때...1+2+4=7 ...7을 입력)

(defun c:ius()  
   (setvar "osmode" 161) 
   (prompt "\n ** 끝점(1) + 교차점(32) + 수직점(128) Osnap 만 활성화되었습니다. \n")
   (princ)
) 

;[스냅코드 목록]

;끝점       1 [v]
;중간점   2 
;중심점   4 
;노드       8 
;사분점   16 
;교차점   32 [v]
;연장선   4096
;삽입점   64
;수직점   128 [v]
;접점       256
;근처점   512
