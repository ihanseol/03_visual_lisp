(defun c:diet()
  (setq osm (getvar "osmode"))
  (command "audit" "y" "")
  (command "-purge" "a" "*" "n")
  (command "deleteghost" "")
  (command "deletelayerfilter" "y")
  (command "elevremove" "all" "")
  (command "-scalelistedit" "r" "y" "e")
  (pdd)
  (pxx)
  (bdd)
  (tdd)
  (kdd)
  (setvar "osmode" osm)
  (command "qsave")
(princ)
)


(defun pdd(/ a i al tt ke xy xy_list w_list k j)
(command "cmdecho" 0)
(command "undo" "g")
(setq a (ssget "all" '((0 . "LWPOLYLINE"))))
(if (null a)
(setq a (ssget "x" '((0 . "LWPOLYLINE"))))
)
(if (null a) (exit))
(setq al (sslength a)
	i 0
	j 0
	tt 0
	)
(princ "\n총처리 pline :: ")(princ al)(princ " 중 중복된 POLYLINE을 지웁니다.\n")

(while (> al i)
	(setq en (ssname a i)
		ent (entget en)
		la (cdr (assoc 8 ent))
		i (1+ i)
		j (1+ j)
		w_list nil
	)

	(foreach k ent  
		(if (= 10 (car k)) (setq w_list (append w_list (list (cdr k)))))
	)
	(setq w_list (append w_list (list la)))
	(if (member w_list xy_list)
		(setq tt (1+ tt)
			a (ssdel en a)
			al (1- al)
			en (entdel en)
			i (1- i)
		)
		(setq xy_list (append xy_list (list w_list)))
	)
	(princ "현처리 pline :: ")(princ j)  (princ "\r")
)
(princ "\n")
(princ "지워진 pline :: ")(princ tt) (princ "\n")
(command "undo" "e")
(princ)
)


(defun pxx( / a i al tt ke j k k1 en ent xy_end xy)
(command "undo" "g")
(setvar "cmdecho" 0)
(setvar "osmode" 0)
(setq a (ssget "x" '((0 . "lwpolyline"))))
(if (null a) (exit))
(setq al (sslength a)
	i 0
	j 0
	k1 0
	tt 0
	)
(princ "\n총처리 pline :: ")(princ al)(princ " 중 2개의 중복된 VERTEX를 가진 LINE을 지웁니다.\n")

(while (> al i)
	(setq en (ssname a i)
		ent (entget en)
		j (1+ j)
		xy (cdr (assoc 10 ent))
		k1 0
	)

	(foreach k ent  
		(if (= 10 (car k)) (setq xy_end (cdr k) k1 (1+ k1)))
	)

	(if (and (<= k1 2) (equal xy xy_end))
		(setq tt (1+ tt)
			a (ssdel en a)
			al (1- al)
			en (entdel en)
		)
		(setq i (1+ i))
	)

	(princ "현처리 pline :: ")(princ j)  (princ "\r")
)
(princ "\n")
(princ "지워진 pline :: ")(princ tt) (princ "\n")
(command "undo" "e")
(princ)
)


(defun BDD( / en ent xy ang i al tt ke j xy_list k w_list)
(command "undo" "g")
(setvar "cmdecho" 0)
(setvar "osmode" 0)
(setq a (ssget "x" '((0 . "INSERT,TEXT"))))
(if (null a) (exit))
(setq al (sslength a)
	i 0
	j 0
	tt 0
	)
(princ "\n총처리 Block,Text :: ")(princ al)(princ " 중 중복된 BLOCK을 지웁니다.\n")

(while (> al i)
	(setq en (ssname a i)
		ent (entget en)
		j (1+ j)
		xy (cdr (assoc 10 ent))
		name (cdr (assoc 2 ent))
		w_list (list xy name)
	)
	(if (member w_list xy_list)
		(setq tt (1+ tt)
			a (ssdel en a)
			al (1- al)
			en (entdel en)
		)
		(setq xy_list (append xy_list (list w_list)) i (1+ i))
	)

	(princ "현처리 Block,Text :: ")(princ j)  (princ "\r")
)

(princ "\n")
(princ "지워진 Block,Text :: ")(princ tt) (princ "\n")
(command "undo" "e")
(princ)
)



(defun tdd( / en ent a b bl bn i al tt ke j w_list )
(command "undo" "g")
(setvar "cmdecho" 0)
(setvar "osmode" 0)
(setq a  (ssget "x" '((0 . "text")(1 . ""))))
(if a (command "erase" a ""))
(setq a (ssget "x" '((0 . "TEXT"))))
(if (null a) (exit))
(setq al (sslength a)
	i 0
	j 0
	tt 0
	ke (ssadd)
	)
(setvar "cecolor" "bylayer")
(setvar "celtype" "bylayer")
(princ "\n총처리 Text :: ")(princ al)(princ "\n")

(while (> al i)
	(setq en (ssname a i)
		ent (entget en)
		i (1+ i)
		xy (cdr (assoc 10 ent))	
		handle (cdr (assoc 5 ent))
		layer (cdr (assoc 8 ent))
		ang (cdr (assoc 50 ent))
		size (cdr (assoc 40 ent))
		text (cdr (assoc 1 ent))
		xy0 (caadr (textbox ent))
		xy1 (polar xy ang xy0)
		xy2 (polar xy1 (+ (/ pi 2) ang) size)
		xy3 (polar xy (+ (/ pi 2) ang) size)
		xyc (polar xy (angle xy xy2) (/ (distance xy xy2) 2))
	)
	(command "zoom" "c" xyc (* xy0 2))
	(setq b (ssget "cp" (list xy xy1 xy2 xy3 xy) (list (cons 1 text)(cons 8 layer))))
	(if b (progn
		(setq bl (sslength b)
			j 0)
		(while (> bl j)
			(setq bn (ssname b j)
				bent (entget bn)
				bhand (cdr (assoc 5 bent))
				j (1+ j)
			)
			(if (/= bhand handle)
				(setq tt (1+ tt)
					j (1+ j)
					a (ssdel bn a)
					bn (entdel bn)
					al (1- al)
				)
			)
		)
	))
	(princ "현처리 Text :: ")(princ i)(princ "\r")
)
(command "zoom" "e")
(princ "\n")
(princ "지워진 Text :: ")(princ tt) (princ "\n")
(command "undo" "e")
(princ)
)

(defun kDD()
(setvar "cmdecho" 0)
(command "undo" "g")
(setq ss (ssget "x" '((0 . "TEXT"))))
(if (null ss) (exit))
(setq ssl (sslength ss)
	i 0
	k 0)

(princ "\n 총처리 Text :: ")(princ ssl)(princ "\n")

(while (> ssl i)
	(setq en (ssname ss i)
		ent (entget en)
		tv1 (cdr (assoc 1 ent))
		tv tv1
		i (1+ i)
	)
(if (/= tv1 "")(progn
	(setq tl 1)
	(while (= (substr tv tl 1) " ")
			(setq tv (substr tv 2))
	)
	(if (= tv "") (entdel en))
	(if (/= tv tv1)
		(setq ent (subst (cons 1 tv) (assoc 1 ent) ent)
			ent (entmod ent)
			k (1+ k))
	)
	(setq tv tv1)
	(setq tl (strlen tv))
	(while (= (substr tv tl) " ")
			(setq tv (substr tv 1 (1- tl)))
			(setq tl (1- tl))
	)	
	(if (= tv "") (entdel en))
	(if (/= tv tv1)
		(setq ent (subst (cons 1 tv) (assoc 1 ent) ent)
			ent (entmod ent)
			k (1+ k)
		)
	)
)
(progn
	(setq k (1+ k))
	(entdel en)
))
(princ "\r 현처리 Text :: ")(princ i) (princ " 중:")(princ k)(princ "수정 ")
)

(command "undo" "e")
(princ)
)
