;;忙式式式式式式式式式式式式式式式式式式式式式式式式式式式式式式忖
;;弛program name : 旋濠蒂 摹曖 陝紫縑 蜃蹺橫 薑溺ж朝 Щ煎斜極  弛
;;弛program by   : kang min soo                                 弛
;;弛date         : 2003.8.7                                     弛
;;弛e-mail       : kang0669@chol.com                            弛
;;戌式式式式式式式式式式式式式式式式式式式式式式式式式式式式式式戎

(defun c:tA(/ tex lin t1 t2 ta l1 l2 lsp lep laa)
   (setvar "cmdecho" 0)
       (setq tex (entsel "\n>>僥濠蒂 摹鷗ж褊衛蹂! : "))
       (setq lin (entsel "\n>>塭檣擊 摹鷗ж褊衛蹂! : "))
       (setq t1 (car tex)
             t2 (entget t1)
             ta (assoc 50 t2)
             l1 (car lin)
             l2 (entget l1)
       )
       (setq lsp (cdr (assoc 10 l2)))
       (setq lep (cdr (assoc 11 l2)))
       (setq laa (angle lsp lep))
         (if (and (> laa 1.5708) (<= laa 4.71239))
            (setq laa (angle lep lsp))
         ) 
         (if (and (<= laa 1.5708) (> laa 4.71239))
            (setq laa (angle lep lsp))
         )
       (setq t2 (subst (cons 50 laa) ta t2))
       (entmod t2)
  (princ)
)
