(defun c:mct (/ os base baseent base10 base11 newdist index ent old10 old11 ang closspoint po1 po2) 
  (defun dtr (a) (* pi (/ a 180.0))) 
  (prompt " MTC = Multy Cross Trim ") 
  (setq os (getvar "osmode")) 
  (setvar "osmode" 0) 
  (setvar "cmdecho" 0) 
  (terpri) 
  (if (= cv_distance nil) (setq cv_distance 10.0)) 
  (setq base (entsel "\n 기준선 선택 : ")) 
  (if base 
    (progn 
      (if (= (cdr (assoc 0 (entget (car base)))) "LINE") 
        (progn 
          (setq baseent (entget (car base))) 
          (setq base10 (cdr (assoc 10 baseent))) 
          (setq base11 (cdr (assoc 11 baseent))) 
          (setq newdist (getreal (strcat "\n 거리값 <" (rtos cv_distance) "> : "))) 
          (if newdist (setq cv_distance newdist)) 
          (while (setq ss (ssget ":s")) 
            (setq index 0) 
            (repeat (sslength ss) 
              (setq ent (entget (ssname ss index))) 
              (if (= (cdr (assoc 0 ent)) "LINE") 
                (progn 
                  (setq old10 (cdr (assoc 10 ent))) 
                  (setq old11 (cdr (assoc 11 ent))) 
                  (setq ang (angle old10 old11)) 
                  (if (inters base10 base11 old10 old11) 
                    (progn 
                      (setq closspoint (inters base10 base11 old10 old11)) 
                      (setq po1 (polar closspoint ang cv_distance)) 
                      (setq po2 (polar closspoint (+ (dtr 180) ang) cv_distance)) 
                      (command "break" (ssname ss index) po1 po2) 
                    ) 
                  ) 
                ) 
              ) 
              (setq index (1+ index)) 
            ) 
          ) 
        ) 
      ) 
    ) 
  ) 
  (setvar "cmdecho" 1) 
  (setvar "osmode" os) 
  (princ) 
)
