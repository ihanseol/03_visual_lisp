(defun c:bte (/ sel_t bname ent old0 old1 new1) 
  (princ "\n 블럭내 텍스트 수정") 
  (command "undo" "g") 
  (while (setq sel_t (nentsel "\n 텍스트선택 ")) 
    (if (> (length sel_t) 2) 
      (setq bname (cdr (assoc 2 (entget (car (last sel_t)))))) 
      (setq bname nil) 
    ) 
    (setq ent (entget (car sel_t))) 
    (setq old0 (cdr (assoc 0 ent))) 
    (if (= old0 "TEXT") 
      (progn 
        (setq old1 (assoc 1 ent)) 
        (setq new1 (getstring t (strcat "\n 새문자<" (cdr old1) "> : "))) 
        (if (/= new1 "") 
          (progn 
            (entmod (subst (cons 1 new1) old1 ent)) 
            (if bname 
              (progn 
                (setq ssbl (ssget "x" (list (cons 2 bname)))) 
                (setq index 0) 
                (repeat (sslength ssbl) 
                  (setq ent (ssname ssbl index)) 
                  (entupd ent) 
                  (setq index (1+ index)) 
                ) 
              ) 
            ) 
          ) 
        ) 
      ) 
    ) 
  ) 
  (command "undo" "e") 
  (princ) 
)
