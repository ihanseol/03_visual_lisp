(defun c:blp (/ ss os ent old10 new10 bname old41 old50 newss b en blp addents ang dist index)
  (setq ss (entsel "\n 블럭 선택 : "))
  (if ss
    (progn
      (command "undo" "g")
      (setq os (getvar "osmode"))
      (setq ent (entget (car ss)))
      (if (= (cdr (assoc 0 ent)) "INSERT")
        (progn
          (setq old10 (cdr (assoc 10 ent)))
          (setvar "osmode" 111)
          (setq new10 (getpoint old10 "\n 새 기준점 : "))
          (if new10
            (progn
              (setvar "osmode" 0)
              (setq bname (cdr (assoc 2 ent)))
              (setq old41 (cdr (assoc 41 ent)))
              (setq old50 (cdr (assoc 50 ent)))
              (if (> old41 0)
                (setq new10 (polar old10 (- (angle old10 new10) old50) (/ (distance old10 new10) old41)))
                (setq new10 (polar old10 (- old50 (angle old10 new10)) (/ (distance old10 new10) old41)))
              )
              (setq newss (ssadd))
              (if (setq b (tblsearch "block" bname))
                (if (setq en (cdr (assoc -2 b)))
                  (progn
                    (setq blp (cdr (assoc 10 b)))
                    (setq ent (entget en))
                    (entmake ent)
                    (setq addents (entlast))
                    (ssadd addents newss)
                    (while (setq en (entnext en))
                      (setq ent (entget en))
                      (entmake ent)
                      (setq addents (entlast))
                      (ssadd addents newss)
                    )
                    (command "block" bname "y" (polar blp (angle old10 new10) (distance old10 new10)) newss "")
                    (setq ang (angle old10 new10))
                    (setq dist (distance new10 old10))
                    (setq ss (ssget "x" (list (cons 2 bname))))
                    (setq index 0)
                    (repeat (sslength ss)
                      (setq ent (entget (ssname ss index)))
                      (setq old10 (cdr (assoc 10 ent)))
                      (setq old41 (cdr (assoc 41 ent)))
                      (setq old50 (cdr (assoc 50 ent)))
                      (if (> old41 0)
                        (setq new10 (polar old10 (+ old50 ang) (* dist old41)))
                        (setq new10 (polar old10 (- old50 ang) (* dist old41)))
                      )
                      (entmod (subst (cons 10 new10) (assoc 10 ent) ent))
                      (setq index (1+ index))
                    )
                  )
                )
              )
	    )
	  )
          (setvar "osmode" os)
	)
      )
      (command "undo" "e")
    )
  )
  (princ)
)
