;;;기본1 - 쓰지 마세요
(defun c:bap1()
	(command "break" pause "f" pause "@")
)
;;;기본2 - 쓰지 마세요
(defun c:bap2()
	(command "break" (entsel) (getpoint) "@")
)
;;;기본3 - 쓰지 마세요
(defun c:bap3(/ entname br_pt)
	(setq entname (car (entsel "\nSelect Single Object\n")))
	(setq br_pt (getpoint "\nPick Point\n"))
	(command "break" entname br_pt "@")
	(princ)
)
;;;선택 객체 1개를 직접 선택. 선택한 객체 위에 있는 1개의 포인트만 허용
(defun c:bap4(/ entname br_pt)
	(setvar "cmdecho" 0)
	(while
		(progn 
			(setvar 'errno 0)
			(setq entname (car (entsel "\nSelect Object\n")))
    			(if (= 7 (getvar 'errno))
				(princ "\nMissed, try again\n")
			)
           	)
        )
	(while
		(progn
			(setq br_pt (getpoint "\nPick Point\n"))
			(if (= nil (vlax-curve-getdistatpoint (vlax-ename->vla-object entname) br_pt))
				(princ "\nPoint is not on curve\n")
			)
		)
	)
	(command "break" entname br_pt "@")
	(princ "Done!")
	(princ)
)
;;;도면 전체 객체에 대해서 1개의 포인트만 허용. 점이 객체 위에 있지 않거나, 객체의 시작점 혹은 끝점일 경우, Failed 메세지 띄우기. 쓰지 마세요
;;;curve가 아닌 객체(치수, 블록 등)가 도면에 있을 경우, 중간에 오류 반환.
;;;curve만 있을 경우에도 객체가 너무 많으면 느림.
(defun c:bap5(/ lastent ss br_pt ss_entname)
	(setvar "cmdecho" 0)
	(setq lastent (entlast))
	(setq ss (ssget "X"))
	(setq br_pt (getpoint "\nPick Point\n"))
	(repeat (sslength ss)
		(setq ss_entname (ssname ss 0))
		(if (/= nil (vlax-curve-getdistatpoint (vlax-ename->vla-object ss_entname) br_pt))
			(command "break" ss_entname br_pt "@")
		)
		(setq ss (ssdel ss_entname ss))
	)
	(if (equal lastent (entlast))
		(princ "\nFailed to Break. Point is not on curve or is end point\n")
		(princ "Done!")
	)
	(princ)
)
;;;선택한 객체들에 대해서 1개의 포인트만 허용. 객체 위에 점이 없을 경우, Failed 메세지 띄우기. 닫힌 원과 타원도 지원하지 않기 때문에 Failed 메세지가 나옵니다.
;;;(setq ss (ssget))에서 필터를 넣으면, 특정 객체만 골라서 선택할 수 있어요.
;;;ex) 순서대로...
;;;(ssget '((0 . "LINE,LWPOLYLINE,CIRCLE,ARC,ELLIPSE,SPLINE,RAY,XLINE"))) - 선, 폴리선, 원, 호, 타원, 스플라인, 광선, X선만 골라서 선택
;;;(ssget '((0 . "*LINE"))) - 선, 폴리선, 스플라인, X선만 골라서 선택
;;;(ssget '((-4 . "<NOT") (0 . "CIRCLE") (-4 . "NOT>"))) - 원만 빼고 선택
;;;(ssget '((-4 . "<NOT") (0 . "CIRCLE,RAY,*LINE") (-4 . "NOT>"))) - 원, 광선, 선, 폴리선, 스플라인, X선 빼고 선택
;;;(ssget "X" '((0 . "*LINE"))) - 도면의 모든 선, 폴리선, 스플라인, X선 선택
(defun c:bap6(/ lastent ss br_pt ss_entname)
	(setvar "cmdecho" 0)
	(setq lastent (entlast))
	(setq ss (ssget '((0 . "LINE,LWPOLYLINE,CIRCLE,ARC,ELLIPSE,SPLINE,RAY,XLINE"))))
	(setq br_pt (getpoint "\nPick Point\n"))
	(repeat (sslength ss)
		(setq ss_entname (ssname ss 0))
		(if (/= nil (vlax-curve-getdistatpoint (vlax-ename->vla-object ss_entname) br_pt))
			(command "break" ss_entname br_pt "@")
		)
		(setq ss (ssdel ss_entname ss))
	)
	(if (equal lastent (entlast))
		(princ "\nFailed to Break. Closed Circle and Ellipse is unsupported\n")
		(princ "Done!")
	)
	(princ)
)
;;;선택한 객체들에 대해서 1개의 포인트만 허용. 원, 타원, 닫힌 폴리선 위에 점이 있을 경우, 미세하게 끊어내고, 그 외의 객체에 대해선 입력한 점으로 끊음.
;;;타원의 경우, 미세하게 끊을 때에 오차가 작동하여 끊기지 않는 경우도 발생할 수 있으므로 권장하지 않음.
(defun c:bap7(/ ss br_pt ss_entname ss_entname_vl br_pt_cl)
	(setvar "cmdecho" 0)
	(setq ss (ssget '((0 . "LINE,LWPOLYLINE,CIRCLE,ARC,ELLIPSE,SPLINE,RAY,XLINE"))))
	(setq br_pt (getpoint "\nPick Point\n"))
	(repeat (sslength ss)
		(setq ss_entname (ssname ss 0))
		(setq ss_entname_vl (vlax-ename->vla-object ss_entname))
		(if (/= nil (vlax-curve-getdistatpoint (vlax-ename->vla-object ss_entname) br_pt))
			(cond
				((wcmatch (cdr (assoc 0 (entget ss_entname))) "LINE,ARC,RAY,XLINE")(command "break" ss_entname br_pt "@"))
				((wcmatch (cdr (assoc 0 (entget ss_entname))) "CIRCLE,ELLIPSE")
				 (progn
					(setq br_pt_cl (vlax-curve-getpointatdist ss_entname_vl (+ (vlax-curve-getdistatpoint ss_entname_vl br_pt) 0.0001)))
					(command "break" ss_entname "none" br_pt "none" br_pt_cl)
				 ))
				((and
					(wcmatch (cdr (assoc 0 (entget ss_entname))) "LWPOLYLINE,SPLINE")
					(vlax-curve-isclosed ss_entname_vl)
				 )
				 (progn
					(setq br_pt_cl (vlax-curve-getpointatdist ss_entname_vl (+ (vlax-curve-getdistatpoint ss_entname_vl br_pt) 0.0001)))
					(command "break" ss_entname "none" br_pt "none" br_pt_cl)
				 ))
				(command "break" ss_entname br_pt "@")
			)
		)
		(setq ss (ssdel ss_entname ss))
	)
	(princ)
)
;;;객체를 선택할 때에 선, 폴리선, 원, 타원, 스플라인, 광선, X선만 골라서 선택. 
;;;선택한 객체들에 대해서 원이나 닫힌 타원은 두 점에서 끊고, 닫힌 폴리선일 경우엔 미세하게 끊어냄.
;;;그 외의 객체에 대해선 입력한 점으로 끊음. 여러 포인트를 계속 허용. 끝내려면 ESC
(defun c:bap8(/ *error* ss br_pt ss_entname ss_entname_vl br_pt_cl  br_pt2 stp stp_new etp etp_new n temp_edata)
	(defun *error* (message)
		(vla-endundomark (vla-get-activedocument (vlax-get-acad-object)))
		(princ "\nEND\n")
		(princ)
	)
	(setvar "cmdecho" 0)
	(vla-startundomark (vla-get-activedocument (vlax-get-acad-object)))
	(setq ss (ssget '((0 . "LINE,LWPOLYLINE,CIRCLE,ARC,ELLIPSE,SPLINE,RAY,XLINE"))))
	(setq n (sslength ss))
	(while (setq br_pt (getpoint "\nPick Point\n"))
		(while (setq ss_entname (ssname ss (1- n)))
			(setq ss_entname_vl (vlax-ename->vla-object ss_entname))
			(if (/= nil (vlax-curve-getdistatpoint (vlax-ename->vla-object ss_entname) br_pt))
				(cond
					((wcmatch (cdr (assoc 0 (entget ss_entname))) "LINE,ARC,RAY,XLINE")
					 (progn	
						(command "break" ss_entname br_pt "@")
						(ssadd (entlast) ss)
					 ))
					((wcmatch (cdr (assoc 0 (entget ss_entname))) "CIRCLE")
					 (progn
						(setq br_pt2 (getpoint "\nPick Second Point\n"))
						(setq temp_edata (entget ss_entname))
						(command "break" ss_entname "none" br_pt "none" br_pt2)
						(entmake temp_edata)
						(setq temp_entname (entlast))
						(command "break" temp_entname "none" br_pt2 "none" br_pt)
						(setq br_pt2 nil)
						(setq temp_edata nil)
						(setq temp_entname nil)
						(ssadd (entlast) ss)
					 ))
					((and
						(wcmatch (cdr (assoc 0 (entget ss_entname))) "ELLIPSE")
						(vlax-curve-isClosed ss_entname_vl)
					 )
					 (progn
						(setq br_pt2 (getpoint "\nPick Second Point\n"))
						(command "break" ss_entname "none" br_pt "none" br_pt2)
						(setq temp_edata (entget ss_entname))
						(setq stp (assoc 41 temp_edata))
						(setq etp (assoc 42 temp_edata))
						(setq stp_new (cons 42 (cdr stp)))
						(setq etp_new (cons 41 (cdr etp)))
						(setq temp_edata (subst stp_new stp temp_edata))
						(setq temp_edata (subst etp_new etp temp_edata))
						(entmake temp_edata)
						(setq br_pt2 nil)
						(setq temp_edata nil)
						(setq stp nil)
						(setq etp nil)
						(setq stp_new nil)
						(setq etp_new nil)
					 ))
					((and
							(wcmatch (cdr (assoc 0 (entget ss_entname))) "LWPOLYLINE,SPLINE")
						(vlax-curve-isclosed ss_entname_vl)
					 )
					 (progn
						(setq br_pt_cl (vlax-curve-getpointatdist ss_entname_vl (+ (vlax-curve-getdistatpoint ss_entname_vl br_pt) 0.0001)))
					(command "break" ss_entname "none" br_pt "none" br_pt_cl)
					 ))
					(t
					 (progn
						(command "break" ss_entname br_pt "@")
						(ssadd (entlast) ss)
					 ))
				)
			)
			(setq n (1- n))
		)
		(setq n (sslength ss))
	)
	(vla-endundomark (vla-get-activedocument (vlax-get-acad-object)))
	(princ)
)
